# initialStateRequirements

## 001-01: Room Interface (Functional)
Each room must get problem constants ( C matrix), heater status ( H) and global system state ( X) as it's input and generate it's current temperature ( which is indicated by x_i for i'th room )

## 001-02: Room state constraints (Functional)
The temperature of each room must depends on it's neighbours temperature, outside temperature and the heater ( if any exists).
The room temperature must not depends on it's previous temperature,

## 002-01: Controller output constraints (Functional)
The controller should be able to generate approperiate outputs for entire system ( which is composed of rooms and controller itself ) in each time step without delay for each room.

## 002-02: Controller initialization (Functional)
The controller must be able to initiate itself with respect to the data defined by the user in the Memory component without any configuration ( by user ) at compile time.

## 003-01: System statement (Functional)
User of the system must be able to configure the whole system easily by changing the memory component of the system. also he must be able to describe the outside weather if it's needed.

## 004-01: Bus constraints and uses (Functional)
The system must contain minimum amount of ports, also define interface for main variables ( such as H,C,X ). Due to lack of support for buses with multiple inputs, try to come up with strategies to reduce the port usage.

## 005-01: System History (Functional)
User of the system must be able to get the result of the system for specific time span he desires.
